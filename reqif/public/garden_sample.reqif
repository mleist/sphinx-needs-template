# Garden requirements export

## CLS_DECISION: Decision
An architectural or organisational decision.

**Slots**

- `id` → `string`
- `title` → `string` *(required)*
- `description` → `string`
- `tags` → `string`
- `status` → `StatusEnum`
- `links` → `string`

**Inherits from:** Need
- Status: open
- Tags: need

## CLS_FUNCTIONAL_REQUIREMENT: FunctionalRequirement
A capability the system must provide.

**Slots**

- `derives` → `string`
- `start_date` → `string`
- `duration` → `integer`
- `id` → `string` *(required)*
- `title` → `string` *(required)*
- `description` → `string`
- `tags` → `string`
- `status` → `StatusEnum`
- `links` → `string`

**Inherits from:** Need
- Status: open
- Tags: need

## CLS_GLOSSARY_TERM: GlossaryTerm
A controlled vocabulary entry.

**Slots**

- `id` → `string` *(required)*
- `title` → `string` *(required)*
- `description` → `string`
- `tags` → `string`
- `status` → `StatusEnum`
- `links` → `string`

**Inherits from:** Need
- Status: open
- Tags: need

## CLS_NON_FUNCTIONAL_REQUIREMENT: NonFunctionalRequirement
A constraint or quality attribute (e.g. noise, water use).

**Slots**

- `derives` → `string`
- `start_date` → `string`
- `duration` → `integer`
- `id` → `string` *(required)*
- `title` → `string` *(required)*
- `description` → `string`
- `tags` → `string`
- `status` → `StatusEnum`
- `links` → `string`

**Inherits from:** Need
- Status: open
- Tags: need

## CLS_RISK: Risk
An identified risk with potential impact on the project.

**Slots**

- `id` → `string` *(required)*
- `title` → `string` *(required)*
- `description` → `string`
- `tags` → `string`
- `status` → `StatusEnum`
- `links` → `string`

**Inherits from:** Need
- Status: open
- Tags: need

## CLS_TEST: Test
A test that verifies one or more requirements.

**Slots**

- `verifies` → `string`
- `id` → `string` *(required)*
- `title` → `string` *(required)*
- `description` → `string`
- `tags` → `string`
- `status` → `StatusEnum`
- `links` → `string`

**Inherits from:** Need
- Status: open
- Tags: need

## CLS_USER_STORY: UserStory
A short user-centric description of a desired outcome.

**Slots**

- `area` → `AreaEnum` *(required)*
- `implements` → `string`
- `id` → `string` *(required)*
- `title` → `string` *(required)*
- `description` → `string`
- `tags` → `string`
- `status` → `StatusEnum`
- `links` → `string`

**Inherits from:** Need
- Status: open
- Tags: need

## CLS_USE_CASE: UseCase
A concrete interaction scenario.

**Slots**

- `implements` → `string`
- `start_date` → `string`
- `duration` → `integer`
- `id` → `string` *(required)*
- `title` → `string` *(required)*
- `description` → `string`
- `tags` → `string`
- `status` → `StatusEnum`
- `links` → `string`

**Inherits from:** Need
- Status: open
- Tags: need

## DEC_BATTERY_MOWER: Battery mower over petrol mower
We adopt a cordless battery mower for the back-yard lawn. Trade-off:
shorter operating window per charge, but lower noise (helps with
NFR_NOISE_WINDOW) and no fuel storage at home.
- Status: accepted
- Tags: mowing

## DEC_ORGANIC_FERT: Use organic compost instead of mineral fertiliser
We use organic compost for the vegetable and flower beds. Trade-off: slower
nutrient release in spring, but lower water-table contamination risk and
better long-term soil structure.
- Status: accepted
- Tags: planting

## FR_FLOWER_PLAN: Flower-bed planting plan
The system SHOULD generate a planting plan for the flower bed that lists
species, quantities and spacing, given a target bloom date and the bed's
dimensions.
- Status: open
- Tags: planting;party_prep

## FR_FRONT_TRIM_LIST: Trim-list generator
The system SHOULD produce a checklist of trim locations (driveway edge,
walkway edge, mailbox surround) so that the front yard is consistently
prepared before any planned event.
- Status: open
- Tags: mowing;party_prep

## FR_HARVEST_ESTIMATE: Harvest-day estimate
Given a planting date and a maturity duration, the system MUST report the
remaining days until harvest. The result is non-negative; produce that is
already mature reports zero remaining days.
- Status: implemented
- Tags: planting

## FR_MOW_WEATHER: Mowing-weather check
The system MUST decide whether the lawn can be mowed today based on
temperature and recent precipitation. Mowing is permitted only when the
temperature is at or above 8 °C and there has been no rain in the
previous reading window.
- Status: implemented
- Tags: mowing

## FR_PARTY_CAPACITY: Patio-capacity calculation
The system MUST estimate how many guests can comfortably stand on the patio
based on its area and a configurable area-per-guest factor (default 1.5 m²).
Negative or zero areas yield a capacity of zero.
- Status: implemented
- Tags: party_prep

## FR_PARTY_TIMELINE: Party-task timeline
The system SHOULD generate a backwards timeline of preparation tasks
counting down to the party day (e.g. "−14 days: refresh flower bed",
"−1 day: mow lawn").
- Status: open
- Tags: party_prep

## G_MATURITY_DAYS: Maturity days
The expected number of days from planting to harvestability for a given
vegetable variety, as printed on seed packets. Used by
`days_until_harvest()`.
- Status: open
- Tags: planting

## G_MOWING_WINDOW: Mowing window
The legally and practically permissible time of day during which a power
lawn mower may be operated in a residential area. See `NFR_NOISE_WINDOW`.
- Status: open
- Tags: mowing

## G_PATIO: Patio
The paved area immediately behind the house, used for outdoor dining and
hosting the small garden party.
- Status: open
- Tags: party_prep

## NFR_NOISE_WINDOW: Lawn-mower noise window
Lawn mowing MUST happen between 09:00 and 18:00 on weekdays and between
10:00 and 18:00 on Saturdays. Mowing is forbidden on Sundays and public
holidays per local quiet-hours regulations.
- Status: accepted
- Tags: mowing

## NFR_PARTY_LEAD_TIME: Party preparation lead time
Preparation activities (mowing, trimming, planting) MUST begin no later
than 14 days before any planned garden party so that flower beds and lawn
have time to recover and bloom.
- Status: accepted
- Tags: party_prep

## NFR_WATER_BUDGET: Vegetable-bed water budget
Watering of the vegetable bed MUST not exceed 30 litres per square metre
per week during dry periods, to keep within the household's seasonal water
allowance.
- Status: accepted
- Tags: planting

## RSK_PESTS_VEG: Pest damage to vegetable bed
Aphids and slugs can decimate young tomato seedlings within days.
Mitigation: install copper barriers, use companion planting (basil),
and inspect plants every other morning.
- Status: open
- Tags: planting

## RSK_RAIN_PARTY: Rain on party day
Heavy rain on the planned party day would force the event indoors or
require last-minute tent rental. Mitigation: monitor the forecast 7 days
ahead and pre-book a tent if probability exceeds 40 %.
- Status: open
- Tags: party_prep

## UC_MOW_BACK_LAWN: Mow the back-yard lawn
Weekly Saturday morning routine.

1. Check weather and grass moisture (see `garden_helper.is_mowing_weather`).
2. Mow lawn in alternating directions.
3. Empty grass catcher into compost bin.
4. Sweep clippings off the patio.
- Status: accepted
- Tags: mowing

## UC_PLANT_VEG_BED: Plant tomatoes and herbs in the vegetable bed
One-off planting day after the last frost.

1. Loosen and amend soil with compost.
2. Plant tomato seedlings 60 cm apart, stake each.
3. Sow basil and parsley seeds in the front row.
4. Water generously and apply mulch.
- Status: in_progress
- Tags: planting

## UC_PREPARE_GARDEN_PARTY: Prepare the patio for a small garden party
Week-long preparation leading up to the party day.

1. Refresh flower bed two weeks ahead.
2. Trim front-yard edges three days ahead.
3. Mow back-yard lawn the day before.
4. Set up tables, string lights and barbecue on party day.
- Status: open
- Tags: party_prep

## US_FRONT_LAWN_TRIM: Trim the front-yard edges before guests arrive
As a **homeowner** I want the lawn edges along the driveway and walkway
trimmed before any planned event so that the front of the house looks
well kept from the street.
- Status: accepted
- Tags: mowing;party_prep

## US_HOST_PARTY: Host a small garden party on the patio
As a **host** I want to set up tables, lighting and a barbecue area on
the patio so that 10–15 guests can comfortably enjoy a Saturday
afternoon garden party.
- Status: open
- Tags: party_prep

## US_MOW_LAWN: Keep the back-yard lawn freshly cut
As a **homeowner** I want my back-yard lawn mowed weekly during the
growing season so that the lawn stays healthy and looks tidy when
visitors arrive.
- Status: accepted
- Tags: mowing;weekly

## US_PLANT_FLOWERS: Refresh the flower bed with seasonal flowers
As a **homeowner** I want the front flower bed replanted with bright
seasonal flowers two weeks before the garden party so that the
arrangement is in full bloom by the time guests arrive.
- Status: open
- Tags: planting;party_prep

## US_PLANT_VEGGIES: Plant tomatoes and herbs in the vegetable bed
As a **hobby gardener** I want to plant tomatoes, basil and parsley in
the south-facing vegetable bed in May so that I can harvest fresh
produce throughout the summer.
- Status: in_progress
- Tags: planting;spring
